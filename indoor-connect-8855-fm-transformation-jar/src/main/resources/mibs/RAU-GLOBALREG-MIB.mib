--
-- RAU-GLOBALREG-MIB.my
-- MIB generated by MG-SOFT Visual MIB Builder Version 6.0  Build 88
-- Saturday, March 27, 2021 at 10:51:36
--

--  RAU-GLOBALREG-MIB.my
-- MIB generated by MG-SOFT Visual MIB Builder Version 6.0  Build 88
-- Friday, March 22, 2019 at 09:34:43
-- 

	RAU-GLOBALREG-MIB DEFINITIONS ::= BEGIN
 
		IMPORTS
			ericsson, ericssonModules			
				FROM ERICSSON-TOP-MIB			
			MODULE-IDENTITY, OBJECT-IDENTITY			
				FROM SNMPv2-SMI;
	
	
-- March 11, 2019 at 14:58 GMT
-- March 11, 2019 at 14:59 GMT
		-- 1.3.6.1.4.1.193.235
		rau MODULE-IDENTITY 
			LAST-UPDATED "201903111458Z"		-- March 11, 2019 at 14:58 GMT
			ORGANIZATION 
				"Ericsson"
			CONTACT-INFO 
				"Contact-info."
			DESCRIPTION 
				"The root of the OID tree assigned to
				Ericsson by the Internet Assigned Numbers
				Authority (IANA)"
			REVISION "201903111459Z"		-- March 11, 2019 at 14:59 GMT
			DESCRIPTION 
				"Ericsson"
			::= { ericsson 235 }

		
	
--
-- Node definitions
--
	
		-- 1.3.6.1.4.1.193.235.1
		rauGeneric OBJECT-IDENTITY
			STATUS current
			DESCRIPTION 
				"rau generic object identify"
			::= { rau 1 }

		
		-- 1.3.6.1.4.1.193.235.1.1
		system OBJECT-IDENTITY
			STATUS current
			DESCRIPTION 
				"rau system object identify, it's for software."
			::= { rauGeneric 1 }

		
		-- 1.3.6.1.4.1.193.235.1.1.1
		systemMIB OBJECT-IDENTITY
			STATUS current
			DESCRIPTION 
				"systemMIB object identify"
			::= { system 1 }

		
		-- 1.3.6.1.4.1.193.235.1.1.2
		notificationMIB OBJECT-IDENTITY
			STATUS current
			DESCRIPTION 
				"notificationMIB object identify"
			::= { system 2 }

		
		-- 1.3.6.1.4.1.193.235.1.1.3
		softwareMIB OBJECT-IDENTITY
			STATUS current
			DESCRIPTION 
				"softwareMIB object identify"
			::= { system 3 }

		
		-- 1.3.6.1.4.1.193.235.1.1.5
		userMgmtMIB OBJECT-IDENTITY
			STATUS current
			DESCRIPTION 
				"userMgmtMIB object identify"
			::= { system 5 }

		
		-- 1.3.6.1.4.1.193.235.1.1.6
		statisticsMIB OBJECT-IDENTITY
			STATUS current
			DESCRIPTION 
				"statisticsMIB object identify"
			::= { system 6 }

		
		-- 1.3.6.1.4.1.193.235.1.2
		equipment OBJECT-IDENTITY
			STATUS current
			DESCRIPTION 
				"rau equipment object identify"
			::= { rauGeneric 2 }

		
		-- 1.3.6.1.4.1.193.235.1.2.1
		cardMIB OBJECT-IDENTITY
			STATUS current
			DESCRIPTION 
				"cardMIB object identify"
			::= { equipment 1 }

		
		-- 1.3.6.1.4.1.193.235.1.2.2
		rfPortMIB OBJECT-IDENTITY
			STATUS current
			DESCRIPTION 
				"rfPortMIB object identify"
			::= { equipment 2 }

		
		-- 1.3.6.1.4.1.193.235.1.2.3
		alarmPanelMIB OBJECT-IDENTITY
			STATUS current
			DESCRIPTION 
				"alarmPanelMIB object identify"
			::= { equipment 3 }

		
		-- 1.3.6.1.4.1.193.235.1.2.4
		fanMIB OBJECT-IDENTITY
			STATUS current
			DESCRIPTION 
				"fanMIB object identify"
			::= { equipment 4 }

		
		-- 1.3.6.1.4.1.193.235.1.2.5
		opticalPortMIB OBJECT-IDENTITY
			STATUS current
			DESCRIPTION 
				"opticalPortMIB object identify"
			::= { equipment 5 }

		
		-- 1.3.6.1.4.1.193.235.1.3
		donorCarrierMIB OBJECT-IDENTITY
			STATUS current
			DESCRIPTION 
				"donorCarrierMIB object identify"
			::= { rauGeneric 3 }

		
		-- 1.3.6.1.4.1.193.235.1.4
		rauContextDefine OBJECT-IDENTITY
			STATUS current
			DESCRIPTION 
				"rauContextDefine object identify"
			::= { rauGeneric 4 }

		
	
	END

--
-- RAU-GLOBALREG-MIB.my
--
