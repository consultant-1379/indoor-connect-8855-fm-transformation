--
-- RAU-NOTIFICATION-MIB.my
-- MIB generated by MG-SOFT Visual MIB Builder Version 6.0  Build 88
-- Tuesday, July 20, 2021 at 10:06:49
--

--  RAU-NOTIFICATION-MIB.my
-- MIB generated by MG-SOFT Visual MIB Builder Version 6.0  Build 88
-- Tuesday, April 16, 2019 at 15:35:31
-- 

	RAU-NOTIFICATION-MIB DEFINITIONS ::= BEGIN
 
		IMPORTS
			notificationMIB			
				FROM RAU-GLOBALREG-MIB			
			SnmpAdminString			
				FROM SNMP-FRAMEWORK-MIB			
			OBJECT-GROUP, MODULE-COMPLIANCE, NOTIFICATION-GROUP			
				FROM SNMPv2-CONF			
			Integer32, Unsigned32, OBJECT-TYPE, MODULE-IDENTITY, NOTIFICATION-TYPE			
				FROM SNMPv2-SMI			
			DateAndTime, TEXTUAL-CONVENTION			
				FROM SNMPv2-TC;
	
	
		-- 1.3.6.1.4.1.193.235.1.1.2.1
		notificationMIBModule MODULE-IDENTITY 
			LAST-UPDATED "202103110944Z"		-- March 11, 2021 at 09:44 GMT
			ORGANIZATION 
				"Ericsson"
			CONTACT-INFO 
				"Contact-info."
			DESCRIPTION 
				"Description."
			REVISION "201903130946Z"		-- March 13, 2019 at 09:46 GMT
			DESCRIPTION 
				"Notification MIB, including alarms, conditions, events, and SNMP trap buffer"
			::= { notificationMIB 1 }

		
	
--
-- Textual conventions
--
	
		AlarmMajorType ::= TEXTUAL-CONVENTION
			STATUS current
			DESCRIPTION 
				"Description."
			SYNTAX INTEGER
				{
				all(1),
				cpu(2),
				memory(3),
				temperature(4),
				module(5),
				configuration(6),
				software(7),
				sdrAM(8),
				flash(9),
				rfInput(10),
				pll(11),
				gps(12),
				nic(13),
				i2c(14),
				ip(15),
				backup(16),
				dhcp(17),
				kernel(18),
				ntp(19)
				}

		AlarmMinorType ::= TEXTUAL-CONVENTION
			STATUS current
			DESCRIPTION 
				"Description."
			SYNTAX INTEGER
				{
				cpuHigh(1),
				highUsageOfMemory(2),
				failureOfMemAlloc(3),
				mesgQueueFull(4),
				temperatureHigh(5),
				moduleInitRegisterFail(6),
				moduleResetRegisterFail(7),
				moduleConfigFileLost(8),
				moduleHeartbeatLost(9),
				configDataAndHwVerNotCompatible(10),
				configInitNotEffective(11),
				configDataFileCorrupted(12),
				configDataChgTakeEffectiveAfterReset(13),
				configDataFileIncomplete(14),
				configDataUpgradeFiled(15),
				versionFault(16),
				versionOfSoftAndHdwNotCompatible(17),
				versionOfSoftwareAndDataMismatch(18),
				versionOfMD5ValidationFailed(19),
				userDataFileCorrupted(20),
				sendMsgFailed(21),
				sdramFault(22),
				flashStorageFault(23),
				softwareUpdatesFail(24),
				pllFault(25),
				gpsUnavailable(26),
				nicFault(27),
				opticalNetworkUnitFault(28),
				i2cBusError(29),
				ipConflict(30),
				dhcpFailed(31),
				kernelPartitionSelfCheckFailed(32),
				ntpSyncFailed(33),
				rfSwitchOff(34),
				rfTransmitModuleFault(35),
				rollbackBecauseInvalidSoftUpd(36),
				rollbackBecauseInvalidconfigFileUpd(37),
				boardTypeMismatch(38),
				firmwareBackupFailed(39),
				responseOfConfigInitTimeout(40)
				}

		RauProbableCause ::= TEXTUAL-CONVENTION
			STATUS current
			DESCRIPTION 
				"Description."
			SYNTAX INTEGER
				{
				outOfCPUCycles(1),
				outOfMemory(2),
				highTemperature(3),
				queueSizeExceeded(4),
				softwareEnvironmentProblem(5),
				communicationsTransmitFailure(6),
				equipmentMalfunction(7),
				congestion(8),
				ipConflict(9),
				versionFault(10),
				boardTypeMismatch(11),
				dhcpFail(12)
				}

		RauSpecialProblem ::= TEXTUAL-CONVENTION
			STATUS current
			DESCRIPTION 
				"Description."
			SYNTAX OCTET STRING (SIZE (0..255))

		ProbableCause ::= TEXTUAL-CONVENTION
			STATUS current
			DESCRIPTION 
				"Description."
			SYNTAX INTEGER
				{
				none(0),
				cardInitFail(1),
				dbFull(2),
				dbInvalid(3),
				memFail(4),
				eqptFail(5),
				linkdown(6),
				configFail(7),
				swupgFail(8),
				authFail(9),
				bkupFail(10),
				dataFail(11),
				sfMismatch(12),
				userEqptMismatch(13),
				fpgaTimeout(14),
				fpgaFail(15),
				invalidThreshold(17),
				dataErr(18),
				cardError(19),
				cpuHigh(20),
				tempureHigh(21),
				sotfware(22),
				envrionment(23)
				}

		ManagedObject ::= TEXTUAL-CONVENTION
			STATUS current
			DESCRIPTION 
				"Description."
			SYNTAX INTEGER
				{
				rau(1),
				fieldReplaceableUnit(2),
				climate(3),
				systemFunctions(4),
				plugedInUnit(5),
				sectorEquipmentFunction(6),
				hwUnit(7),
				fanGroup(8),
				riPortref(9),
				diPortref(10),
				log(11),
				backupAndRestore(12),
				ethernetPort(13),
				deviceGroup(14),
				backupSchedule(15)
				}

		InetAddress ::= TEXTUAL-CONVENTION
			STATUS current
			DESCRIPTION 
				"Denotes a generic Internet address.
				
				An InetAddress value is always interpreted within the context
				of an InetAddressType value.  Every usage of the InetAddress
				textual convention is required to specify the InetAddressType
				object that provides the context.  It is suggested that the
				InetAddressType object be logically registered before the
				object(s) that use the InetAddress textual convention, if
				they appear in the same logical row.
				
				The value of an InetAddress object must always be
				consistent with the value of the associated InetAddressType
				object.  Attempts to set an InetAddress object to a value
				inconsistent with the associated InetAddressType
				must fail with an inconsistentValue error.
				
				When this textual convention is used as the syntax of an
				index object, there may be issues with the limit of 128
				sub-identifiers specified in SMIv2, STD 58.  In this case,
				the object definition MUST include a 'SIZE' clause to
				limit the number of potential instance sub-identifiers;
				otherwise the applicable constraints MUST be stated in
				the appropriate conceptual row DESCRIPTION clauses, or
				in the surrounding documentation if there is no single
				DESCRIPTION clause that is appropriate."
			SYNTAX OCTET STRING (SIZE (0..255))

		EventType ::= TEXTUAL-CONVENTION
			STATUS current
			DESCRIPTION 
				"Description."
			SYNTAX INTEGER
				{
				processErrorAlarm(1),
				environmentalAlarm(2),
				qualityofServiceAlarm(3),
				communicationsAlarm(4),
				equipmentAlarm(5),
				intefrityViolation(6),
				opeartionViolation(7),
				physicalViolation(8),
				securityServiceOrMechanismViolation(9),
				timeDomainViolation(10)
				}

		TrapReportType ::= TEXTUAL-CONVENTION
			STATUS current
			DESCRIPTION 
				"Description."
			SYNTAX INTEGER
				{
				reportImmediately(1),
				reportLater(2)
				}

	
--
-- Node definitions
--
	
		-- 1.3.6.1.4.1.193.235.1.1.2.1.1
		rauNotificationObjs OBJECT IDENTIFIER ::= { notificationMIBModule 1 }

		
		-- 1.3.6.1.4.1.193.235.1.1.2.1.1.1
		alarmSummary OBJECT IDENTIFIER ::= { rauNotificationObjs 1 }

		
		-- 1.3.6.1.4.1.193.235.1.1.2.1.1.1.2
		rauAlarmSumCritical OBJECT-TYPE
			SYNTAX Integer32
			MAX-ACCESS read-only
			STATUS current
			DESCRIPTION
				"This object shows the number of currently active
				                alarms with perceived severity 'critical'. Note
				                that only stateful alarms are included."
			::= { alarmSummary 2 }

		
		-- 1.3.6.1.4.1.193.235.1.1.2.1.1.1.3
		rauAlarmSumMajor OBJECT-TYPE
			SYNTAX Integer32
			MAX-ACCESS read-only
			STATUS current
			DESCRIPTION
				"This object shows the number of currently active
				                alarms with perceived severity 'major'. Note
				                that only stateful alarms are included."
			::= { alarmSummary 3 }

		
		-- 1.3.6.1.4.1.193.235.1.1.2.1.1.1.4
		rauAlarmSumMinor OBJECT-TYPE
			SYNTAX Integer32
			MAX-ACCESS read-only
			STATUS current
			DESCRIPTION
				"This object shows the number of currently active
				                alarms with perceived severity 'minor'. Note
				                that only stateful alarms are included."
			::= { alarmSummary 4 }

		
		-- 1.3.6.1.4.1.193.235.1.1.2.1.1.1.5
		rauAlarmSumWarning OBJECT-TYPE
			SYNTAX Integer32
			MAX-ACCESS read-only
			STATUS current
			DESCRIPTION
				"This object shows the number of currently active
				                alarms with perceived severity 'warning'. Note
				                that only stateful alarms are included."
			::= { alarmSummary 5 }

		
		-- 1.3.6.1.4.1.193.235.1.1.2.1.1.1.6
		rauAlarmSwitch OBJECT-TYPE
			SYNTAX INTEGER
				{
				disable(0),
				enable(1)
				}
			MAX-ACCESS read-write
			STATUS current
			DESCRIPTION
				"Controls alarm reporting, 
				     1: enable alarm reporting, 
				     0: disable alarm reporting.
				Default value is 1.
				"
			DEFVAL { enable }
			::= { alarmSummary 6 }

		
		-- 1.3.6.1.4.1.193.235.1.1.2.1.1.1.7
		rauCriticalEnable OBJECT-TYPE
			SYNTAX INTEGER
				{
				disable(0),
				enable(1)
				}
			MAX-ACCESS read-write
			STATUS current
			DESCRIPTION
				"If both rauAlarmSwitch and rauCriticalEnable are set to disable, 
				        critical alarm reporting will be disabled.
				If rauAlarmSwitch is set to disable but rauCriticalEnable is set to enable, 
				        critical alarm reporting will be enabled."
			DEFVAL { enable }
			::= { alarmSummary 7 }

		
		-- 1.3.6.1.4.1.193.235.1.1.2.1.1.1.8
		rauMajorEnable OBJECT-TYPE
			SYNTAX INTEGER
				{
				disable(0),
				enable(1)
				}
			MAX-ACCESS read-write
			STATUS current
			DESCRIPTION
				"If both rauAlarmSwitch and rauMajorEnable are set to disable, 
				     major alarm reporting will be disabled.
				If rauAlarmSwitch is set to disable but rauMajorEnable is set 
				     to enable, major alarm reporting will be enabled."
			DEFVAL { enable }
			::= { alarmSummary 8 }

		
		-- 1.3.6.1.4.1.193.235.1.1.2.1.1.1.9
		rauMinorEnable OBJECT-TYPE
			SYNTAX INTEGER
				{
				disable(0),
				enable(1)
				}
			MAX-ACCESS read-write
			STATUS current
			DESCRIPTION
				"If both rauAlarmSwitch and rauMinorEnable are set to disable, 
				     minor alarm reporting will be disabled.
				If rauAlarmSwitch is set to disable but rauMinorEnable is set 
				     to enable, minor alarm reporting will be enabled."
			DEFVAL { enable }
			::= { alarmSummary 9 }

		
		-- 1.3.6.1.4.1.193.235.1.1.2.1.1.2
		alarmNotifObjects OBJECT IDENTIFIER ::= { rauNotificationObjs 2 }

		
		-- 1.3.6.1.4.1.193.235.1.1.2.1.1.2.6
		alarmNObjRecordType OBJECT-TYPE
			SYNTAX Integer32
			MAX-ACCESS accessible-for-notify
			STATUS current
			DESCRIPTION
				"This is a scalar variable only used in
				                notifications. It tells the management system
				                whether the alarm record being reported in the
				                notification represents a new alarm instance
				                or an update of an existing alarm instance."
			::= { alarmNotifObjects 6 }

		
		-- 1.3.6.1.4.1.193.235.1.1.2.1.1.3
		alarmActiveAlarms OBJECT IDENTIFIER ::= { rauNotificationObjs 3 }

		
		-- 1.3.6.1.4.1.193.235.1.1.2.1.1.3.1
		alarmActiveNumber OBJECT-TYPE
			SYNTAX Integer32
			MAX-ACCESS read-only
			STATUS current
			DESCRIPTION
				"This object shows the total number of currently
				                active alarms, i.e. the total number of entries
				                in the Alarm Table."
			::= { alarmActiveAlarms 1 }

		
		-- 1.3.6.1.4.1.193.235.1.1.2.1.1.3.2
		alarmActiveLastchanged OBJECT-TYPE
			SYNTAX DateAndTime
			MAX-ACCESS read-only
			STATUS current
			DESCRIPTION
				"A timestamp when the active alarm table was last
				                changed. The value can be used by a manager to
				                initiate an alarm resynchronization procedure.
				                NOTE: All fields of the DateAndTime MUST be
				                filled out, including the hours and minutes from
				                UTC. As such, the value should be 11 octets
				                long."
			::= { alarmActiveAlarms 2 }

		
		-- 1.3.6.1.4.1.193.235.1.1.2.1.1.3.3
		alarmActiveLastSequenceNo OBJECT-TYPE
			SYNTAX Integer32
			MAX-ACCESS read-only
			STATUS current
			DESCRIPTION
				"The last used sequence number for an alarm state
				                change notification. A management system can poll
				                this variable in order to detect lost alarm
				                change notifications."
			::= { alarmActiveAlarms 3 }

		
		-- 1.3.6.1.4.1.193.235.1.1.2.1.1.3.5
		alarmActiveTable OBJECT-TYPE
			SYNTAX SEQUENCE OF AlarmActiveEntry
			MAX-ACCESS not-accessible
			STATUS current
			DESCRIPTION
				"This table list all active alarms in the system.
				                The number of entries,active alarms,can be read in
				                alarmActiveNumber. Entries are created when a
				                a new alarm raised. If the same resource has several 
				                active alarms, with different Alarm Types, this will 
				                be represented as separate rows. Rows disappear whenever 
				                the  alarm is cleared in the resource.
				                              "
			::= { alarmActiveAlarms 5 }

		
		-- 1.3.6.1.4.1.193.235.1.1.2.1.1.3.5.1
		alarmActiveEntry OBJECT-TYPE
			SYNTAX AlarmActiveEntry
			MAX-ACCESS not-accessible
			STATUS current
			DESCRIPTION
				"One entry in the table holds one active alarm
				                for a given resource. Entries are created by the
				                system when a resource has a new alarm state.
				                Entries are deleted by the system when a resource
				                alarm state is cleared.
				
				              "
			INDEX { alarmActiveIndex }
			::= { alarmActiveTable 1 }

		
		AlarmActiveEntry ::=
			SEQUENCE { 
				alarmActiveIndex
					Unsigned32,
				alarmActiveMajorType
					OCTET STRING,
				alarmActiveMinorType
					OCTET STRING,
				alarmActiveSpecificProblem
					RauSpecialProblem,
				alarmActiveManagedObject
					OCTET STRING,
				alarmActiveEventType
					OCTET STRING,
				alarmActiveEventTime
					DateAndTime,
				alarmActiveOriginalEventTime
					DateAndTime,
				alarmActiveProbableCause
					OCTET STRING,
				alarmActiveEventSeverity
					OCTET STRING,
				alarmActiveEventOriginalSeverity
					OCTET STRING,
				alarmActiveAdditionalText
					OCTET STRING,
				alarmActiveResourceId
					OBJECT IDENTIFIER,
				alarmActiveAdditionalInfo
					OCTET STRING
			 }

		-- 1.3.6.1.4.1.193.235.1.1.2.1.1.3.5.1.1
		alarmActiveIndex OBJECT-TYPE
			SYNTAX Unsigned32 (1..65535)
			MAX-ACCESS read-only
			STATUS current
			DESCRIPTION
				"A unique value, greater than zero, for each
				                alarm. It is recommended that values are
				                assigned contiguously starting from 1. The value
				                for each alarm must remain constant at least from
				                one re-initialization of the entity to the next
				                re-initialization. Note that this index should
				                not be used for alarm synchronization purposes
				                since the 'logical' index for an alarm is
				                - alarmActiveMajorType
				                - alarmActiveMinorType
				                - alarmActiveManagedObject"
			::= { alarmActiveEntry 1 }

		
		-- 1.3.6.1.4.1.193.235.1.1.2.1.1.3.5.1.2
		alarmActiveMajorType OBJECT-TYPE
			SYNTAX OCTET STRING
			MAX-ACCESS read-only
			STATUS current
			DESCRIPTION
				"In combination with alarmActiveMinorType,
				                this object provides a unique identification of the
				                fault type. Different managed object types and
				                instances can share alarm types, but if the same
				                managed object reports the same alarm type, it is
				                to be considered as the same alarm state. The
				                alarm type is a simplification of the different
				                X.733 and 3GPP alarm IRP alarm correlation
				                mechanisms based on EventType, ProbableCause,
				                SpecificProblem and NotificationId. For systems
				                where alarmActiveMajorType is not needed for
				                identification purposes, it is not used and MUST
				                be zero-valued."
			::= { alarmActiveEntry 2 }

		
		-- 1.3.6.1.4.1.193.235.1.1.2.1.1.3.5.1.3
		alarmActiveMinorType OBJECT-TYPE
			SYNTAX OCTET STRING
			MAX-ACCESS read-only
			STATUS current
			DESCRIPTION
				"In combination with 
				                alarmActiveMajorType, this object provides a unique
				                identification of the fault type, not including
				                the managed object. Different managed object
				                types and instances can share alarm types, but if
				                the same managed object reports the same alarm
				                type, it is to be considered as the same alarm
				                state. The alarm type is a simplification of the
				                different X.733 and 3GPP alarm IRP alarm
				                correlation mechanisms based on EventType,
				                ProbableCause, SpecificProblem and
				                NotificationId."
			::= { alarmActiveEntry 3 }

		
		-- 1.3.6.1.4.1.193.235.1.1.2.1.1.3.5.1.4
		alarmActiveSpecificProblem OBJECT-TYPE
			SYNTAX RauSpecialProblem
			MAX-ACCESS read-only
			STATUS current
			DESCRIPTION
				"This is a clear-text unique identification of
				                the alarm type. There is a one-to-one mapping
				                between alarmActiveSpecificProblem and
				                [alarmActiveMajorType,alarmActiveMinorType]"
			::= { alarmActiveEntry 4 }

		
		-- 1.3.6.1.4.1.193.235.1.1.2.1.1.3.5.1.5
		alarmActiveManagedObject OBJECT-TYPE
			SYNTAX OCTET STRING
			MAX-ACCESS read-only
			STATUS current
			DESCRIPTION
				"The 3GPP naming convention shall be used as
				                format for the managed object parameter. Note
				                that the granularity must be good enough to
				                guarantee unique alarm states and relevant
				                resource identification to the operator.
				                NOTE: The DN should be *relative* to the nodes
				                *own* root."
			::= { alarmActiveEntry 5 }

		
		-- 1.3.6.1.4.1.193.235.1.1.2.1.1.3.5.1.6
		alarmActiveEventType OBJECT-TYPE
			SYNTAX OCTET STRING
			MAX-ACCESS read-only
			STATUS current
			DESCRIPTION
				"ITU Recommendation X.733, 'Information
				                Technology - Open Systems Interconnection -
				                System Management: Alarm Reporting Function',
				                1992"
			::= { alarmActiveEntry 6 }

		
		-- 1.3.6.1.4.1.193.235.1.1.2.1.1.3.5.1.7
		alarmActiveEventTime OBJECT-TYPE
			SYNTAX DateAndTime
			MAX-ACCESS read-only
			STATUS current
			DESCRIPTION
				"A timestamp of the alarm state change event.
				                Note that this variable represents the last
				                change of the alarm state, such as changed severity,
				                additional text/info. If the alarm state has not changed,
				                this variable represents the alarm raise
				                time and will be the same as originalEventTime.
				
				                NOTE: All fields of the DateAndTime MUST be
				                filled out, including the hours and minutes from
				                UTC. As such, the value should be 11 octets
				                long."
			REFERENCE
				"DateAndTime is defined in RFC 2579, page 18.
				                ITU Recommendation X.733, 'Information Technology
				                - Open Systems Interconnection - System
				                Management: Alarm Reporting Function', 1992"
			::= { alarmActiveEntry 7 }

		
		-- 1.3.6.1.4.1.193.235.1.1.2.1.1.3.5.1.8
		alarmActiveOriginalEventTime OBJECT-TYPE
			SYNTAX DateAndTime
			MAX-ACCESS read-only
			STATUS current
			DESCRIPTION
				"The timestamp of the original alarm raise
				                notification.
				                NOTE: All fields of the DateAndTime MUST be
				                filled out, including the hours and minutes from
				                UTC. As such, the value should be 11 octets
				                long."
			REFERENCE
				"DateAndTime is defined in RFC 2579, page 18."
			::= { alarmActiveEntry 8 }

		
		-- 1.3.6.1.4.1.193.235.1.1.2.1.1.3.5.1.9
		alarmActiveProbableCause OBJECT-TYPE
			SYNTAX OCTET STRING
			MAX-ACCESS read-only
			STATUS current
			DESCRIPTION
				"The probable cause for the alarm originally
				                defined by X.733 and subsequent standards. Due to the
				                history of problems in maintaining a standardized
				                probable cause the probable cause is not unique.
				                A best effort mapping of the alarm to existing
				                probable causes is used."
			REFERENCE
				"ITU Recommendation X.733, 'Information
				                Technology - Open Systems Interconnection -
				                System Management: Alarm Reporting Function',
				                1992"
			::= { alarmActiveEntry 9 }

		
		-- 1.3.6.1.4.1.193.235.1.1.2.1.1.3.5.1.10
		alarmActiveEventSeverity OBJECT-TYPE
			SYNTAX OCTET STRING
			MAX-ACCESS read-only
			STATUS current
			DESCRIPTION
				"The severity of the alarm as defined by X.733.
				                Note that this may not be the original severity
				                since the alarm severity may have changed. "
			REFERENCE
				"ITU Recommendation X.733, 'Information
				                Technology - Open Systems Interconnection -
				                System Management: Alarm Reporting Function',
				                1992"
			::= { alarmActiveEntry 10 }

		
		-- 1.3.6.1.4.1.193.235.1.1.2.1.1.3.5.1.11
		alarmActiveEventOriginalSeverity OBJECT-TYPE
			SYNTAX OCTET STRING
			MAX-ACCESS read-only
			STATUS current
			DESCRIPTION
				"The original severity as reported by the alarm
				                raise notification"
			::= { alarmActiveEntry 11 }

		
		-- 1.3.6.1.4.1.193.235.1.1.2.1.1.3.5.1.12
		alarmActiveAdditionalText OBJECT-TYPE
			SYNTAX OCTET STRING
			MAX-ACCESS read-only
			STATUS current
			DESCRIPTION
				"A user friendly text describing the alarm. The
				                text is both static depending on the alarm type
				                (probable cause), and dynamic depending on
				                managed object instance and other conditions.
				                This string is longer than the corresponding
				                varbind in the notification in order to manage
				                large strings."
			REFERENCE
				"ITU Recommendation X.733, 'Information
				                Technology - Open Systems Interconnection -
				                System Management: Alarm Reporting Function',
				                1992"
			::= { alarmActiveEntry 12 }

		
		-- 1.3.6.1.4.1.193.235.1.1.2.1.1.3.5.1.13
		alarmActiveResourceId OBJECT-TYPE
			SYNTAX OBJECT IDENTIFIER
			MAX-ACCESS read-only
			STATUS current
			DESCRIPTION
				"In case the alarm refers to an object which is
				                instrumented by SNMP. This variable indicates the
				                corresponding OID for the managed object."
			REFERENCE
				"RFC 3877 IETF ALARM MIB"
			::= { alarmActiveEntry 13 }

		
		-- 1.3.6.1.4.1.193.235.1.1.2.1.1.3.5.1.14
		alarmActiveAdditionalInfo OBJECT-TYPE
			SYNTAX OCTET STRING
			MAX-ACCESS read-only
			STATUS current
			DESCRIPTION
				"Additional information for the alarm,
								structured in a way that is suitable for
								machine to machine communication.
				                This string is longer than the corresponding
				                varbind in the notification in order to manage
				                large strings."
			::= { alarmActiveEntry 14 }

		
		-- 1.3.6.1.4.1.193.235.1.1.2.1.1.4
		alarmAlerts OBJECT IDENTIFIER ::= { rauNotificationObjs 4 }

		
		-- 1.3.6.1.4.1.193.235.1.1.2.1.1.4.1
		alarmAlertNumber OBJECT-TYPE
			SYNTAX Integer32
			MAX-ACCESS read-only
			STATUS current
			DESCRIPTION
				"The number of rows in the alert table."
			::= { alarmAlerts 1 }

		
		-- 1.3.6.1.4.1.193.235.1.1.2.1.1.4.2
		alarmAlertLastChanged OBJECT-TYPE
			SYNTAX DateAndTime
			MAX-ACCESS read-only
			STATUS current
			DESCRIPTION
				"A timestamp when the alert table was last
				                changed. Can be used by a manager to initiate 
				                an update of alerts procedure.
				                NOTE: All fields of the DateAndTime MUST be
				                filled out, including the hours and minutes from
				                UTC. As such, the value should be 11 octets
				                long."
			::= { alarmAlerts 2 }

		
		-- 1.3.6.1.4.1.193.235.1.1.2.1.1.4.3
		alarmAlertLastSequenceNo OBJECT-TYPE
			SYNTAX Integer32
			MAX-ACCESS read-only
			STATUS current
			DESCRIPTION
				"The last sequence number used in alert
				                notifications. It can be used to detect a lost
				                notification."
			::= { alarmAlerts 3 }

		
		-- 1.3.6.1.4.1.193.235.1.1.2.1.1.4.5
		alarmAlertTable OBJECT-TYPE
			SYNTAX SEQUENCE OF AlarmAlertEntry
			MAX-ACCESS not-accessible
			STATUS current
			DESCRIPTION
				"This table lists the last alerts in the system.
				                An alert is a stateless event, that is no clear
				                notification will be sent. Rows in this table are
				                created when a new alert event is detected. Rows
				                are deleted by the instrumentation at a
				                predefined size or age."
			::= { alarmAlerts 5 }

		
		-- 1.3.6.1.4.1.193.235.1.1.2.1.1.4.5.1
		alarmAlertEntry OBJECT-TYPE
			SYNTAX AlarmAlertEntry
			MAX-ACCESS not-accessible
			STATUS current
			DESCRIPTION
				"One entry in the table holds one alert for a
				                given resource. Rows in this table are created
				                when a new alert is detected. Rows are deleted
				                by the instrumentation at a predefined size or
				                age."
			INDEX { alarmAlertIndex }
			::= { alarmAlertTable 1 }

		
		AlarmAlertEntry ::=
			SEQUENCE { 
				alarmAlertIndex
					Unsigned32,
				alarmAlertMajorType
					OCTET STRING,
				alarmAlertMinorType
					OCTET STRING,
				alarmAlertSpecificProblem
					OCTET STRING,
				alarmAlertManagedObject
					OCTET STRING,
				alarmAlertEventType
					OCTET STRING,
				alarmAlertEventTime
					DateAndTime,
				alarmAlertProbableCause
					OCTET STRING,
				alarmAlertSeverity
					OCTET STRING,
				alarmAlertAdditionalText
					OCTET STRING,
				alarmAlertResourceId
					OBJECT IDENTIFIER,
				alarmAlertAdditionalInfo
					OCTET STRING
			 }

		-- 1.3.6.1.4.1.193.235.1.1.2.1.1.4.5.1.1
		alarmAlertIndex OBJECT-TYPE
			SYNTAX Unsigned32 (1..65535)
			MAX-ACCESS read-only
			STATUS current
			DESCRIPTION
				"Index in the alert table"
			::= { alarmAlertEntry 1 }

		
		-- 1.3.6.1.4.1.193.235.1.1.2.1.1.4.5.1.2
		alarmAlertMajorType OBJECT-TYPE
			SYNTAX OCTET STRING
			MAX-ACCESS read-only
			STATUS current
			DESCRIPTION
				"In combination with alarmAlertMinorType, this object
				                provides unique identification of the alert.
						This is a simplification of the different X.733
				                and 3GPP alarm IRP alarm correlation mechanisms
				                based on EventType, ProbableCause,
				                SpecificProblem and NotificationId."
			::= { alarmAlertEntry 2 }

		
		-- 1.3.6.1.4.1.193.235.1.1.2.1.1.4.5.1.3
		alarmAlertMinorType OBJECT-TYPE
			SYNTAX OCTET STRING
			MAX-ACCESS read-only
			STATUS current
			DESCRIPTION
				"In combination with alarmAlertMajorType, this object
				                provides a unique identification of the alert.
						This is a simplification of the different X.733
				                and 3GPP alarm IRP alarm correlation mechanisms
				                based on EventType, ProbableCause,
				                SpecificProblem and NotificationId."
			::= { alarmAlertEntry 3 }

		
		-- 1.3.6.1.4.1.193.235.1.1.2.1.1.4.5.1.4
		alarmAlertSpecificProblem OBJECT-TYPE
			SYNTAX OCTET STRING
			MAX-ACCESS read-only
			STATUS current
			DESCRIPTION
				"This is a clear-text unique identification of
				                the alert type. There is a one-to-one mapping
				                between alarmAlertSpecificProblem and
				                [alarmAlertMajorType, alarmAlertMinorType]"
			::= { alarmAlertEntry 4 }

		
		-- 1.3.6.1.4.1.193.235.1.1.2.1.1.4.5.1.5
		alarmAlertManagedObject OBJECT-TYPE
			SYNTAX OCTET STRING
			MAX-ACCESS read-only
			STATUS current
			DESCRIPTION
				"The 3GPP naming convention shall be used as
				                format for the managed object parameter. Note
				                that the granularity must be good enough to
				                guarantee relevant resource identification to the
				                operator.
				                NOTE: The DN should be *relative* to the nodes
				                *own* root."
			REFERENCE
				"3GPP TS 32.106-8 V3.2, Name convention for
				                Managed Objects"
			::= { alarmAlertEntry 5 }

		
		-- 1.3.6.1.4.1.193.235.1.1.2.1.1.4.5.1.6
		alarmAlertEventType OBJECT-TYPE
			SYNTAX OCTET STRING
			MAX-ACCESS read-only
			STATUS current
			DESCRIPTION
				"The event type as defined in X.733/X.736."
			REFERENCE
				"ITU Recommendation X.733, 'Information
				                Technology - Open Systems Interconnection -
				                System Management: Alarm Reporting Function',
				                1992"
			::= { alarmAlertEntry 6 }

		
		-- 1.3.6.1.4.1.193.235.1.1.2.1.1.4.5.1.7
		alarmAlertEventTime OBJECT-TYPE
			SYNTAX DateAndTime
			MAX-ACCESS read-only
			STATUS current
			DESCRIPTION
				"A timestamp of the alert. NOTE: All fields of
				                the DateAndTime MUST be filled out, including the
				                hours and minutes from UTC. As such, the value
				                should be 11 octets long."
			REFERENCE
				"DateAndTime is defined in RFC 2579, page 18.
				                ITU Recommendation X.733, 'Information Technology
				                - Open Systems Interconnection - System
				                Management: Alarm Reporting Function', 1992"
			::= { alarmAlertEntry 7 }

		
		-- 1.3.6.1.4.1.193.235.1.1.2.1.1.4.5.1.8
		alarmAlertProbableCause OBJECT-TYPE
			SYNTAX OCTET STRING
			MAX-ACCESS read-only
			STATUS current
			DESCRIPTION
				"The probable cause, originally defined by X.733 
				                and subsequent standards. Due to the
				                history of problems in maintaining a standardized
				                probable cause the probable cause is not unique.
				                A best effort mapping of the alert to existing
				                probable causes is used."
			REFERENCE
				"ITU Recommendation X.733, 'Information
				                Technology - Open Systems Interconnection -
				                System Management: Alarm Reporting Function',
				                1992"
			::= { alarmAlertEntry 8 }

		
		-- 1.3.6.1.4.1.193.235.1.1.2.1.1.4.5.1.9
		alarmAlertSeverity OBJECT-TYPE
			SYNTAX OCTET STRING
			MAX-ACCESS read-only
			STATUS current
			DESCRIPTION
				"The severity of the alert as defined by X.733"
			REFERENCE
				"ITU Recommendation X.733, 'Information
				                Technology - Open Systems Interconnection -
				                System Management: Alarm Reporting Function',
				                1992"
			::= { alarmAlertEntry 9 }

		
		-- 1.3.6.1.4.1.193.235.1.1.2.1.1.4.5.1.10
		alarmAlertAdditionalText OBJECT-TYPE
			SYNTAX OCTET STRING
			MAX-ACCESS read-only
			STATUS current
			DESCRIPTION
				"A user friendly text describing the alert. The
				                text is both static depending on the alert type
				                and dynamic depending on managed object and other
				                conditions."
			REFERENCE
				"ITU Recommendation X.733, 'Information
				                Technology - Open Systems Interconnection -
				                System Management: Alarm Reporting Function',
				                1992"
			::= { alarmAlertEntry 10 }

		
		-- 1.3.6.1.4.1.193.235.1.1.2.1.1.4.5.1.11
		alarmAlertResourceId OBJECT-TYPE
			SYNTAX OBJECT IDENTIFIER
			MAX-ACCESS read-only
			STATUS current
			DESCRIPTION
				"In case the alert refers to an object which is
				                instrumented by SNMP, this variable indicates the
				                corresponding OID for the managed object."
			REFERENCE
				"RFC 3877 IETF ALARM MIB"
			::= { alarmAlertEntry 11 }

		
		-- 1.3.6.1.4.1.193.235.1.1.2.1.1.4.5.1.12
		alarmAlertAdditionalInfo OBJECT-TYPE
			SYNTAX OCTET STRING
			MAX-ACCESS read-only
			STATUS current
			DESCRIPTION
				"Additional information for the alert,
								structured in a way that is suitable for
								machine to machine communication.
				                This string is longer than the corresponding
				                varbind in the notification in order to manage
				                large strings."
			::= { alarmAlertEntry 12 }

		
		-- 1.3.6.1.4.1.193.235.1.1.2.1.1.5
		alarmHeartBeat OBJECT IDENTIFIER ::= { rauNotificationObjs 5 }

		
		-- 1.3.6.1.4.1.193.235.1.1.2.1.1.5.1
		alarmHbInterval OBJECT-TYPE
			SYNTAX Integer32 (0..86399)
			UNITS "s"
			MAX-ACCESS read-write
			STATUS current
			DESCRIPTION
				"The notification alarmHeartBeatNotif will be
				                sent by every alarmHbInterval. Managers can
				                subscribe to the notification using the SNMP
				                framework MIBS by using the snmpNotifyName
				                'heartbeat'. 0 means no need send trap to NMS."
			DEFVAL { 180 }
			::= { alarmHeartBeat 1 }

		
		-- 1.3.6.1.4.1.193.235.1.1.2.1.1.5.2
		alarmHeartbeatString OBJECT-TYPE
			SYNTAX SnmpAdminString
			MAX-ACCESS accessible-for-notify
			STATUS current
			DESCRIPTION
				"Alarm heartbeat string, it will be sent to NMS."
			DEFVAL { "Heartbeat" }
			::= { alarmHeartBeat 2 }

		
		-- 1.3.6.1.4.1.193.235.1.1.2.1.1.5.3
		noNmsContactTimeout OBJECT-TYPE
			SYNTAX Integer32 (0..86399)
			UNITS "s"
			MAX-ACCESS read-write
			STATUS current
			DESCRIPTION
				"NMS will get the alarm information periodically. This parameter 
				    is used to set the interval.
				 A value of 0 will suppress the no OAM/NMS contact alarm."
			DEFVAL { 1200 }
			::= { alarmHeartBeat 3 }

		
		-- 1.3.6.1.4.1.193.235.1.1.2.1.2
		alarmNotifications OBJECT IDENTIFIER ::= { notificationMIBModule 2 }

		
		-- 1.3.6.1.4.1.193.235.1.1.2.1.2.1
		rauNotifPrefix OBJECT IDENTIFIER ::= { alarmNotifications 1 }

		
		-- 1.3.6.1.4.1.193.235.1.1.2.1.2.1.2
		alarmWarning NOTIFICATION-TYPE
			OBJECTS { alarmActiveManagedObject, alarmActiveMajorType, alarmActiveMinorType, alarmActiveSpecificProblem, alarmActiveLastSequenceNo, 
				alarmActiveEventType, alarmActiveEventTime, alarmActiveProbableCause, alarmActiveAdditionalText, alarmActiveAdditionalInfo, 
				alarmNObjRecordType }
			STATUS current
			DESCRIPTION 
				"This notification is sent when a resource
				                detects a new alarm state with severity warning.
				                The notification is also used to change severity,
				                additional text and/or additional info
				                of an alarm. The alarmNObjRecordType
				                varbind indicates whether this is a new alarm
				                instance or an update to an existing alarm instance.
				                
				                The combination of ManagedObject and 
				                MajorType/MinorType is always unique and can be
				                used by management systems to correlate alarms,
				                change alarms, and clear alarms. A corresponding
				                row will be created in the alarm table
				                (alarmActiveTable). The sequence number
				                will increase for every notification and can be
				                used to detect lost notifications.
				
				                A management system should be prepared for
				                appending text to additional text, indicated by
				                the alarmNObjMoreAdditionalText varbind, and
				                sent with alarmAppendInfo. (Note do not
				                confuse this with a change of additional text.)
				
				                A management system should be prepared for
				                appending text to additional info, indicated by
				                the alarmNObjMoreAdditionalInfo varbind, and
				                sent with alarmAppendInfo.  (Note do not
				                confuse this with a change of additional info.)
				
				                A management system should also be prepared to
				                receive a resource ID (OID) identifying the
				                alarming resource if the system sending the
				                notification can provide that information. In
				                that case, alarmNObjResourceId will be set to
				                'true' and the resource ID will be sent in an
				                alarmAppendInfo notification."
			::= { rauNotifPrefix 2 }

		
		-- 1.3.6.1.4.1.193.235.1.1.2.1.2.1.3
		alarmMinor NOTIFICATION-TYPE
			OBJECTS { alarmActiveManagedObject, alarmActiveMajorType, alarmActiveMinorType, alarmActiveSpecificProblem, alarmActiveLastSequenceNo, 
				alarmActiveEventType, alarmActiveEventTime, alarmActiveProbableCause, alarmActiveAdditionalText, alarmActiveAdditionalInfo, 
				alarmNObjRecordType }
			STATUS current
			DESCRIPTION 
				"This notification is sent when a resource
				                detects a new minor alarm state with severity minor.
				                The notification is also used to change severity,
				                additional text and/or additional info
				                of an alarm. The alarmNObjRecordType
				                varbind indicates whether this is a new alarm
				                instance or an update to an existing alarm instance.
				                
				                The combination of ManagedObject and 
				                MajorType/MinorType is always unique and can be
				                used by management systems to correlate alarms,
				                change alarms, and clear alarms. A corresponding
				                row will be created in the alarm table
				                (alarmActiveTable). The sequence number
				                will increase for every notification and can be
				                used to detect lost notifications.
				
				                A management system should be prepared for
				                appending text to additional text, indicated by
				                the alarmNObjMoreAdditionalText varbind, and
				                sent with alarmAppendInfo. (Note do not
				                confuse this with a change of additional text.)
				
				                A management system should be prepared for
				                appending text to additional info, indicated by
				                the alarmNObjMoreAdditionalInfo varbind, and
				                sent with alarmAppendInfo.  (Note do not
				                confuse this with a change of additional info.)
				
				                A management system should also be prepared to
				                receive a resource ID (OID) identifying the
				                alarming resource if the system sending the
				                notification can provide that information. In
				                that case, alarmNObjResourceId will be set to
				                'true' and the resource ID will be sent in an
				                alarmAppendInfo notification."
			::= { rauNotifPrefix 3 }

		
		-- 1.3.6.1.4.1.193.235.1.1.2.1.2.1.4
		alarmMajor NOTIFICATION-TYPE
			OBJECTS { alarmActiveManagedObject, alarmActiveMajorType, alarmActiveMinorType, alarmActiveSpecificProblem, alarmActiveLastSequenceNo, 
				alarmActiveEventType, alarmActiveEventTime, alarmActiveProbableCause, alarmActiveAdditionalText, alarmActiveAdditionalInfo, 
				alarmNObjRecordType }
			STATUS current
			DESCRIPTION 
				"This notification is sent when a resource
				                detects a new major alarm state with severity major.
				                The notification is also used to change severity,
				                additional text and/or additional info
				                of an alarm. The alarmNObjRecordType
				                varbind indicates whether this is a new alarm
				                instance or an update to an existing alarm instance.
				                
				                The combination of ManagedObject and 
				                MajorType/MinorType is always unique and can be
				                used by management systems to correlate alarms,
				                change alarms, and clear alarms. A corresponding
				                row will be created in the alarm table
				                (alarmActiveTable). The sequence number
				                will increase for every notification and can be
				                used to detect lost notifications.
				
				                A management system should be prepared for
				                appending text to additional text, indicated by
				                the alarmNObjMoreAdditionalText varbind, and
				                sent with alarmAppendInfo. (Note do not
				                confuse this with a change of additional text.)
				
				                A management system should be prepared for
				                appending text to additional info, indicated by
				                the alarmNObjMoreAdditionalInfo varbind, and
				                sent with alarmAppendInfo.  (Note do not
				                confuse this with a change of additional info.)
				
				                A management system should also be prepared to
				                receive a resource ID (OID) identifying the
				                alarming resource if the system sending the
				                notification can provide that information. In
				                that case, alarmNObjResourceId will be set to
				                'true' and the resource ID will be sent in an
				                alarmAppendInfo notification."
			::= { rauNotifPrefix 4 }

		
		-- 1.3.6.1.4.1.193.235.1.1.2.1.2.1.5
		alarmCritical NOTIFICATION-TYPE
			OBJECTS { alarmActiveManagedObject, alarmActiveMajorType, alarmActiveMinorType, alarmActiveSpecificProblem, alarmActiveLastSequenceNo, 
				alarmActiveEventType, alarmActiveEventTime, alarmActiveProbableCause, alarmActiveAdditionalText, alarmActiveAdditionalInfo, 
				alarmNObjRecordType }
			STATUS current
			DESCRIPTION 
				"This notification is sent when a resource
				                detects a new critical alarm state with severity critical.
				                The notification is also used to change severity,
				                additional text and/or additional info
				                of an alarm. The alarmNObjRecordType
				                varbind indicates whether this is a new alarm
				                instance or an update to an existing alarm instance.
				                
				                The combination of ManagedObject and 
				                MajorType/MinorType is always unique and can be
				                used by management systems to correlate alarms,
				                change alarms, and clear alarms. A corresponding
				                row will be created in the alarm table
				                (alarmActiveTable). The sequence number
				                will increase for every notification and can be
				                used to detect lost notifications.
				
				                A management system should be prepared for
				                appending text to additional text, indicated by
				                the alarmNObjMoreAdditionalText varbind, and
				                sent with alarmAppendInfo. (Note do not
				                confuse this with a change of additional text.)
				
				                A management system should be prepared for
				                appending text to additional info, indicated by
				                the alarmNObjMoreAdditionalInfo varbind, and
				                sent with alarmAppendInfo.  (Note do not
				                confuse this with a change of additional info.)
				
				                A management system should also be prepared to
				                receive a resource ID (OID) identifying the
				                alarming resource if the system sending the
				                notification can provide that information. In
				                that case, alarmNObjResourceId will be set to
				                'true' and the resource ID will be sent in an
				                alarmAppendInfo notification."
			::= { rauNotifPrefix 5 }

		
		-- 1.3.6.1.4.1.193.235.1.1.2.1.2.1.6
		alarmCleared NOTIFICATION-TYPE
			OBJECTS { alarmActiveManagedObject, alarmActiveMajorType, alarmActiveMinorType, alarmActiveSpecificProblem, alarmActiveLastSequenceNo, 
				alarmActiveEventType, alarmActiveEventTime, alarmActiveProbableCause, alarmActiveAdditionalText, alarmActiveAdditionalInfo, 
				alarmNObjRecordType }
			STATUS current
			DESCRIPTION 
				"This notification is sent when a resource
				                detects a cleared alarm state. The combination
				                of ManagedObject and MajorType/MinorType is
				                always unique and shall be used by management
				                systems to correlate alarms and clear alarms. The
				                corresponding row in the alarm table(alarmActiveAlarmTable)
				                will be deleted. The sequence number will increase for every
				                notification and can be used to detect lost notifications. 
				                
				                Note that it should not be required to send an
								append trap for a cleared alarm. Those varbinds
								which flag that an append trap will follow are 
								kept here for backward compatibility reasons."
			::= { rauNotifPrefix 6 }

		
		-- 1.3.6.1.4.1.193.235.1.1.2.1.2.1.9
		alarmWarnAlert NOTIFICATION-TYPE
			OBJECTS { alarmAlertManagedObject, alarmAlertMajorType, alarmAlertMinorType, alarmAlertSpecificProblem, alarmAlertLastSequenceNo, 
				alarmAlertEventType, alarmAlertEventTime, alarmAlertProbableCause, alarmAlertAdditionalText, alarmAlertAdditionalInfo
				 }
			STATUS current
			DESCRIPTION 
				"This notification is sent when a resource
				                detects a new alert with severity warning. A
				                corresponding row will be created in the alert
				                table. The sequence number will increase for
				                every notification and can be used to detect lost
				                notifications."
			::= { rauNotifPrefix 9 }

		
		-- 1.3.6.1.4.1.193.235.1.1.2.1.2.1.10
		alarmMinorAlert NOTIFICATION-TYPE
			OBJECTS { alarmAlertManagedObject, alarmAlertMajorType, alarmAlertMinorType, alarmAlertSpecificProblem, alarmAlertLastSequenceNo, 
				alarmAlertEventType, alarmAlertEventTime, alarmAlertProbableCause, alarmAlertAdditionalText, alarmAlertAdditionalInfo
				 }
			STATUS current
			DESCRIPTION 
				"This notification is sent when a resource
				                detects a new alert with severity minor. A
				                corresponding row will be created in the alert
				                table. The sequence number will increase for
				                every notification and can be used to detect lost
				                notifications."
			::= { rauNotifPrefix 10 }

		
		-- 1.3.6.1.4.1.193.235.1.1.2.1.2.1.11
		alarmMajorAlert NOTIFICATION-TYPE
			OBJECTS { alarmAlertManagedObject, alarmAlertMajorType, alarmAlertMinorType, alarmAlertSpecificProblem, alarmAlertLastSequenceNo, 
				alarmAlertEventType, alarmAlertEventTime, alarmAlertProbableCause, alarmAlertAdditionalText, alarmAlertAdditionalInfo
				 }
			STATUS current
			DESCRIPTION 
				"This notification is sent when a resource
				                detects a new alert with severity major. A
				                corresponding row will be created in the alert
				                table. The sequence number will increase for
				                every notification and can be used to detect lost
				                notifications."
			::= { rauNotifPrefix 11 }

		
		-- 1.3.6.1.4.1.193.235.1.1.2.1.2.1.12
		alarmCriticalAlert NOTIFICATION-TYPE
			OBJECTS { alarmAlertManagedObject, alarmAlertMajorType, alarmAlertMinorType, alarmAlertSpecificProblem, alarmAlertLastSequenceNo, 
				alarmAlertEventType, alarmAlertEventTime, alarmAlertProbableCause, alarmAlertAdditionalText, alarmAlertAdditionalInfo
				 }
			STATUS current
			DESCRIPTION 
				"This notification is sent when a resource
				                detects a new alert with severity critical. A
				                corresponding row will be created in the alert
				                table. The sequence number will increase for
				                every notification and can be used to detect lost
				                notifications."
			::= { rauNotifPrefix 12 }

		
		-- 1.3.6.1.4.1.193.235.1.1.2.1.2.1.14
		alarmHeartBeatNotif NOTIFICATION-TYPE
			OBJECTS { alarmHeartbeatString, alarmActiveLastchanged, alarmActiveLastSequenceNo, alarmAlertLastChanged, alarmAlertLastSequenceNo
				 }
			STATUS current
			DESCRIPTION 
				"This is a heartbeat notification with interval
				                according to the alarmHbInterval. It contains
				                the last sequence numbers used for alarms and
				                alarm events. These varbinds can be used to
				                detect lost notifications.
				
				                The notification alarmHeartBeatNotif will be
				                sent every alarmHbInterval. Managers can
				                subscribe to the notification using the SNMP
				                framework MIBs by using the snmpNotifyName
				                'heartbeat'. (SNMP-NOTIFICATION-MIB,
				                snmpNotifyTable)."
			::= { rauNotifPrefix 14 }

		
		-- 1.3.6.1.4.1.193.235.1.1.2.1.3
		notificationConf OBJECT IDENTIFIER ::= { notificationMIBModule 3 }

		
		-- 1.3.6.1.4.1.193.235.1.1.2.1.3.1
		notificationGroups OBJECT IDENTIFIER ::= { notificationConf 1 }

		
		-- 1.3.6.1.4.1.193.235.1.1.2.1.3.1.1
		alarmSummaryGroup OBJECT-GROUP
			OBJECTS { rauAlarmSumCritical, rauAlarmSumMajor, rauAlarmSumMinor, rauAlarmSumWarning, rauAlarmSwitch, 
				rauCriticalEnable, rauMajorEnable, rauMinorEnable }
			STATUS current
			DESCRIPTION 
				"Alarm summary scalar group"
			::= { notificationGroups 1 }

		
		-- 1.3.6.1.4.1.193.235.1.1.2.1.3.1.2
		alarmActiveAlarmsGroup OBJECT-GROUP
			OBJECTS { alarmActiveNumber, alarmActiveLastchanged, alarmActiveLastSequenceNo, alarmActiveMajorType, alarmActiveMinorType, 
				alarmActiveSpecificProblem, alarmActiveManagedObject, alarmActiveEventType, alarmActiveEventTime, alarmActiveProbableCause, 
				alarmActiveEventSeverity, alarmActiveIndex, alarmActiveAdditionalInfo, alarmActiveEventOriginalSeverity, alarmActiveOriginalEventTime, 
				alarmActiveResourceId, alarmActiveAdditionalText }
			STATUS current
			DESCRIPTION 
				"Active alarm table group"
			::= { notificationGroups 2 }

		
		-- 1.3.6.1.4.1.193.235.1.1.2.1.3.1.3
		alarmAlertAlarmGroup OBJECT-GROUP
			OBJECTS { alarmAlertNumber, alarmAlertLastChanged, alarmAlertLastSequenceNo, alarmAlertMajorType, alarmAlertMinorType, 
				alarmAlertSpecificProblem, alarmAlertManagedObject, alarmAlertEventType, alarmAlertEventTime, alarmAlertProbableCause, 
				alarmAlertResourceId, alarmAlertAdditionalInfo, alarmAlertSeverity, alarmAlertIndex, alarmAlertAdditionalText
				 }
			STATUS current
			DESCRIPTION 
				"Alert alarm table group"
			::= { notificationGroups 3 }

		
		-- 1.3.6.1.4.1.193.235.1.1.2.1.3.1.4
		alarmHeartBeatGroup OBJECT-GROUP
			OBJECTS { alarmHbInterval, alarmHeartbeatString, noNmsContactTimeout }
			STATUS current
			DESCRIPTION 
				"Heartbeat scalar group"
			::= { notificationGroups 4 }

		
		-- 1.3.6.1.4.1.193.235.1.1.2.1.3.1.9
		alarmNotificationGroup OBJECT-GROUP
			OBJECTS { alarmNObjRecordType }
			STATUS current
			DESCRIPTION 
				"Notification scalars group
				                "
			::= { notificationGroups 9 }

		
		-- 1.3.6.1.4.1.193.235.1.1.2.1.3.1.10
		alarmActiveAlarmGroup NOTIFICATION-GROUP
			NOTIFICATIONS { alarmWarning, alarmMinor, alarmMajor, alarmCritical, alarmCleared
				 }
			STATUS current
			DESCRIPTION 
				"Active alarm notifications group"
			::= { notificationGroups 10 }

		
		-- 1.3.6.1.4.1.193.235.1.1.2.1.3.1.12
		alarmAlertNotifGroup NOTIFICATION-GROUP
			NOTIFICATIONS { alarmWarnAlert, alarmMinorAlert, alarmMajorAlert, alarmCriticalAlert }
			STATUS current
			DESCRIPTION 
				"Alert notifications group"
			::= { notificationGroups 12 }

		
		-- 1.3.6.1.4.1.193.235.1.1.2.1.3.1.13
		alarmHeartBeatNotifGroup NOTIFICATION-GROUP
			NOTIFICATIONS { alarmHeartBeatNotif }
			STATUS current
			DESCRIPTION 
				"Heartbeat notifications group"
			::= { notificationGroups 13 }

		
		-- 1.3.6.1.4.1.193.235.1.1.2.1.3.3
		notificationCompliances OBJECT IDENTIFIER ::= { notificationConf 3 }

		
		-- 1.3.6.1.4.1.193.235.1.1.2.1.3.3.1
		notificationCompliance MODULE-COMPLIANCE
			STATUS current
			DESCRIPTION 
				"RAU notification compliance"
			MODULE -- this module
				MANDATORY-GROUPS { alarmSummaryGroup, alarmActiveAlarmsGroup, alarmHeartBeatGroup, alarmAlertAlarmGroup, alarmNotificationGroup, 
					alarmActiveAlarmGroup, alarmAlertNotifGroup, alarmHeartBeatNotifGroup }
			::= { notificationCompliances 1 }

		
	
	END

--
-- RAU-NOTIFICATION-MIB.my
--
